module l3vpn {
    yang-version 1.1;
    namespace "wjl:l3vpn";
    prefix l3vpn;

    import network {
        prefix net;
    }

    import common {
        prefix common;
    }

    include l3vpn-bgp;

    list l3vpn {
        key id;
        leaf id {type string;}
        uses common:qos;
    }
}

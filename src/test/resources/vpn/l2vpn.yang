module l2vpn {
    yang-version 1.1;
    namespace "wjl:l2vpn";
    prefix l2vpn;

    import network {
        prefix net;
    }

    include l2vpn-bfd;
    include l2vpn-oam;
    include l2vpn-vll;

    grouping oam;
    feature oam;
}

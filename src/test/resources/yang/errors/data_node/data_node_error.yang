module ma {
  container c1 {
    list c1 {
      error "conflict with ma line 6 : container c1.";
    }
    choice c1 {
      case c1 {
        leaf-list c1 {
          error "conflict with ma line 6 : container c1.";
        }
      }
      leaf c1 {
        error "conflict with ma line 6 : container c1.";
      }
      choice c2 {
        leaf c2 {
          error "conflict with ma line 13 : container c2.";
        }
      }
    }
  }
  leaf c1 {
    error "conflict with ma line 5 : container c1.";
  }
  leaf c3 {
    error "conflict with sa1 line 34 : leaf c3.";
  }
}

module mb {
  augment "/ma:c4" {
    container c4 {
      error "conflict with mb line 42 : leaf c4.";
    }
  }
  augment "/ma:c4" {
    leaf-list c4 {
      error "conflict with mb line 42 : leaf c4.";
    }
  }
}

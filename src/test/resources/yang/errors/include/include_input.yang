submodule s1 {
  belongs-to ma;
}

submodule s2 {
  belongs-to ma;
  revision 2022-05-01;
  include s1;
}

submodule s3 {
  belongs-to ma;
  revision 2022-05-02;
}

module ma {
  prefix a;
  include s2 {
    revision-date 2022-05-01;
  }
  include s2;
  include s3 {
    revision-date 2022-05-01;
  }
}

module mb {
  prefix b;
  include s99;
  include s2;
}

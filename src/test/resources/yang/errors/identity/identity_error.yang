module mb {
  identity vpn {
    error "conflict with mb line 27 : identity vpn";
  }
  container root {
    leaf t2 {
      type identityref {
        base ma:cloud-vpn {
          error "undefined.";
        }
      }
    }
  }
  identity mb2:oam {
    error "conflict with mb1 line 58 : identity oam.";
  }
}

submodule mb1 {
  identity oam {
    error "circular dependency";
  }
  identity bfd {
    error "circular dependency";
  }
}

submodule mb2 {
  identity oam {
    error "conflict with mb1 line 58 : identity oam.";
  }
}

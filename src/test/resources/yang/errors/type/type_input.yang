module ma {
  yang-version 1.1;
  prefix ma;

  identity vpn;

  typedef phone {
    type string {
      length "13..16";
      pattern "[0-9]{13}";
      pattern "[0-9]{2}-[0-9](13)";
    }
  }

  container number {
    leaf x1 {
      type int8 {
        range "-128..127";
      }
    }
    leaf x2 {
      type int16 {
        range " -32768..32767";
      }
    }
    leaf x3 {
      type int32 {
        range "-2147483648..2147483647";
      }
    }
    leaf x4 {
      type int64 {
        range "-9223372036854775808..9223372036854775807";
      }
    }
    leaf y1 {
      type uint8 {
        range "0..255";
      }
    }
    leaf y2 {
      type uint16 {
        range "0..65535";
      }
    }
    leaf y3 {
      type uint32 {
        range "0..4294967295";
      }
    }
    leaf y4 {
      type uint64 {
        range "0..18446744073709551615";
      }
    }
    leaf z {
      type decimal64 {
        fraction-digits 12;
        range "0..18446744073709551615";
      }
    }
  }

  container other {
    leaf bool {
      type boolean;
    }
    leaf emp {
      type empty;
    }
    leaf bin {
      type binary {
        length 4096;
      }
    }
    leaf enum {
      type enumeration {
        enum OCh;
        enum ODUk;
      }
    }
    leaf bit {
      type bits {
        bit PZ;
        bit PO;
      }
    }
    leaf ref1 {
      type leafref {
        path "/number/x1";
        require-instance false;
      }
    }
    leaf ref2 {
      type identityref {
        base vpn;
      }
    }
    leaf ref3 {
      type instance-identifier {
        require-instance true;
      }
    }
    leaf union {
      type union {
        type int32 {
          range "1..10";
        }
        type string;
        type boolean;
      }
    }
  }
}

module mb {
  yang-version 1.1;
  prefix mb;

  typedef phone {
    type string {
      length 13;
      length 13;
      pattern 666;
    }
  }

  container number {
    leaf x1 {
      type int8 {
        length 13;
      }
    }
  }

  container other {
    leaf bool {
      type boolean {
        description "wrong";
      }
    }
    leaf emp {
      type empty {
        description "wrong";
      }
    }
    leaf bin {
      type binary {
        len 4096;
      }
    }
    leaf enum {
      type enumeration;
    }
    leaf bit {
      type bits;
    }
    leaf ref1 {
      type leafref;
    }
    leaf ref2 {
      type identityref;
    }
    leaf union {
      type union;
    }
  }
}

module ma {
  error "require sub statement prefix.";
}

module mb {
  error "too many sub statement prefix.";
}

module md {
  import ma {
    error "prefix conflict with md.";
  }
  import mc {
    error "prefix conflict with mb.";
  }
  import me {
    error "no matched module.";
  }
}

module mf {
  import mc {
    error "no matched module.";
  }
}

module ta {
    yang-version 1.1;
    namespace "wjl:typedef";
    prefix ta;

    typedef address {
        type string {
            length "1..64";
        }
    }

    container root {}
}

module tb {
    yang-version 1.1;
    namespace "wjl:typedef";
    prefix tb;
    import ta { prefix ta; }

    typedef adr {
        type ta:address;
    }

    typedef ip_v.6 {
        type string;
    }

    grouping rule {
        leaf label {
            type ip_v.6;
        }
    }
}

module tc {
    yang-version 1.1;
    namespace "wjl:typedef";
    prefix tc;
    import ta { prefix ta; }
    import tb { prefix tb; }

    container root {
        leaf id {
            type int32;
        }

        leaf adr {
            type adr;
        }

        typedef adr {
            type tb:adr;
        }
    }

    augment "/ta:root" {
        uses tb:rule;
    }
}
